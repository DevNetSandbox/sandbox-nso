module vlan-tenant {

  namespace "http://example.com/vlan-tenant";
  prefix vlan-tenant;

  import ietf-inet-types {
    prefix inet;
  }
  import tailf-common {
    prefix tailf;
  }
  import tailf-ncs {
    prefix ncs;
  }
  import vlan-fabric {
    prefix vlan-fabric;
  }

  list vlan-tenant {
    key name;
    // TODO: Forbid - in names
    leaf name {
      tailf:info "Unique service id";
      tailf:cli-allow-range;
      type string;
    }

    uses ncs:service-data;
    ncs:servicepoint vlan-tenant;

    leaf fabric {
      type leafref {
        path "/vlan-fabric:vlan-fabric/vlan-fabric:name";
      }
      mandatory true;
    }

    list static-routes {
      key network; 

      leaf network {
        type inet:ipv4-prefix;
      }

      leaf gateway {
        type inet:ipv4-address;
      }
    }

    // TODO: Name, call them VNIs?
    list network {
      key name;

      leaf name {
        // Not used for anything?
        type string;
      }

      leaf vlanid {
        type uint32;
      }

      leaf network {
        type inet:ipv4-prefix;
        mandatory true;
      }

      leaf layer3-on-fabric {
        type boolean; 
        default true;
      }

      leaf build-route-neighbors { 
        type boolean;
        default false;
      }

      leaf dhcp-relay-address {
        type inet:ipv4-address;
      }

      container connections {
        list switch {
          key device; 

          leaf device {
            type leafref {
              path "/vlan-fabric:vlan-fabric[vlan-fabric:name=current()/../../../../fabric]/vlan-fabric:switch/vlan-fabric:device";
            }
          }

          list interface {
            key interface; 

            leaf interface {
              type string; 
              // TODO: Change to a reference to verify actually an interface 
            }

            leaf description { 
              type string; 
            }

            // TODO - Update for the forbidden stuff 
            // FROM EVPN 
            // If the interface is in access, no other connection in any tenant using the same fabric may use the interface
            // Forbidden cases:
            //   1. Different fabric, any segment, any connection
            //   2. Same fabric, different segment, any connection
            // must "mode = 'trunk' or
            //       ((count(/vxlan-tenant:vxlan-tenant[name!=current()/../../name][fabric=current()/../../fabric]/segments/connection[leaf=current()/leaf][iface=current()/iface]) = 0)
            //   and  (count(/vxlan-tenant:vxlan-tenant[name=current()/../../name][fabric=current()/../../fabric]/segments[name!=current()/../name]/connection[leaf=current()/leaf][iface=current()/iface]) = 0))";

            leaf mode { 
              type enumeration {
                enum trunk; 
                enum access; 
              }
              default access;
            }

          }

          list port-channel {
            key portchannel-id; 
            leaf portchannel-id {
              type string; 
            }

            leaf description {
              type string; 
            }

            leaf mode { 
              type enumeration {
                enum trunk; 
                enum access; 
              }
              default access;
            }

            list interface {
              key interface; 

              leaf interface {
                type string; 
              }
              
            }
          }          
        }

        list switch-pair {
          key name; 

          leaf name {
            type leafref {
              path "/vlan-fabric:vlan-fabric[vlan-fabric:name=current()/../../../../fabric]/vlan-fabric:switch-pair/vlan-fabric:name";
            }
          }

          list interface {
            key interface; 

            leaf interface {
              type string; 
              // TODO: Change to a reference to verify actually an interface 
            }

            leaf description { 
              type string; 
            }

            // TODO - Update for the forbidden stuff 
            // FROM EVPN 
            // If the interface is in access, no other connection in any tenant using the same fabric may use the interface
            // Forbidden cases:
            //   1. Different fabric, any segment, any connection
            //   2. Same fabric, different segment, any connection
            // must "mode = 'trunk' or
            //       ((count(/vxlan-tenant:vxlan-tenant[name!=current()/../../name][fabric=current()/../../fabric]/segments/connection[leaf=current()/leaf][iface=current()/iface]) = 0)
            //   and  (count(/vxlan-tenant:vxlan-tenant[name=current()/../../name][fabric=current()/../../fabric]/segments[name!=current()/../name]/connection[leaf=current()/leaf][iface=current()/iface]) = 0))";

            leaf mode { 
              type enumeration {
                enum trunk; 
                enum access; 
              }
              default access;
            }

          }          

          list port-channel {
            key portchannel-id; 
            leaf portchannel-id {
              type string; 
            }

            leaf description {
              type string; 
            }

            leaf mode { 
              type enumeration {
                enum trunk; 
                enum access; 
              }
              default access;
            }

            list interface {
              key interface; 

              leaf interface {
                type string; 
              }
              
            }
          }

        }
      }

      // list connection {
      //   key "leaf iface";
      //   tailf:cli-suppress-mode;

      //   leaf leaf {
      //     tailf:cli-drop-node-name;
      //     type leafref {
      //       path "/vlan-fabric:vlan-fabric[vlan-fabric:name=current()/../../../fabric]/vlan-fabric:leaves/vlan-fabric:device";
      //     }
      //   }

      //   leaf iface {
      //     tailf:cli-drop-node-name;
      //     type string;
      //     // TODO: Consistency check & format
      //   }

      //   // If the interface is in access, no other connection in any tenant using the same fabric may use the interface
      //   // Forbidden cases:
      //   //   1. Different fabric, any segment, any connection
      //   //   2. Same fabric, different segment, any connection
      //   must "mode = 'trunk' or
      //         ((count(/vlan-tenant:vlan-tenant[name!=current()/../../name][fabric=current()/../../fabric]/network/connection[leaf=current()/leaf][iface=current()/iface]) = 0)
      //     and  (count(/vlan-tenant:vlan-tenant[name=current()/../../name][fabric=current()/../../fabric]/network[name!=current()/../name]/connection[leaf=current()/leaf][iface=current()/iface]) = 0))";

      //   leaf mode {
      //     type enumeration {
      //       enum trunk;
      //       enum access;
      //     }
      //     default trunk;
      //   }
      // }
    }




  }
}
